# ================================================================
# FreeCAD Affine Dataset Macro
# BOX
#
# Dataset-generator interface
#
# DATASET_PARAMS_JSON
#
# {
#     "x_half_ratio": ...,
#     "y_half_ratio": ...,
#     "z_half_ratio": ...
# }
#
#
# DATASET_ROTATION_JSON
#
# [
#     qx,
#     qy,
#     qz,
#     qw
# ]
#
#
# Physical realization:
#
#     REALIZATION_SCALE_MM = 10.0
#
#     x_half = x_half_ratio * 10 mm
#     y_half = y_half_ratio * 10 mm
#     z_half = z_half_ratio * 10 mm
#
#     full_x = 2 * x_half
#     full_y = 2 * y_half
#     full_z = 2 * z_half
#
#
# Geometry is generated centered at the origin:
#
#     [-x_half, +x_half]
#     [-y_half, +y_half]
#     [-z_half, +z_half]
#
#
# Rotation is applied independently in SO(3).
#
# No translation is used.
#
# ================================================================


import os
import json
import math

import FreeCAD as App
import Part
import MeshPart


# ================================================================
# CONFIGURATION
# ================================================================

REALIZATION_SCALE_MM = 10.0

LINEAR_DEFLECTION_MM = 0.05

ANGULAR_DEFLECTION_DEG = 5.0

RELATIVE_MESH = False


# ================================================================
# ENVIRONMENT
# ================================================================

def require_environment_variable(name):

    value = os.environ.get(name)

    if value is None or value.strip() == "":

        raise RuntimeError(
            "{} is not defined.".format(name)
        )

    return value


# ================================================================
# LOAD AFFINE PARAMETERS
# ================================================================

def load_affine_parameters():

    raw = require_environment_variable(
        "DATASET_PARAMS_JSON"
    )

    print("")
    print(
        "DATASET_PARAMS_JSON:"
    )

    print(
        raw
    )

    try:

        params = json.loads(
            raw
        )

    except Exception as exc:

        raise RuntimeError(
            "Invalid DATASET_PARAMS_JSON:\n"
            + str(exc)
        )

    if not isinstance(
        params,
        dict
    ):

        raise RuntimeError(
            "DATASET_PARAMS_JSON must contain "
            "a JSON object."
        )

    # ------------------------------------------------------------
    # Support both:
    #
    # {
    #     "x_half_ratio": ...,
    #     "y_half_ratio": ...,
    #     "z_half_ratio": ...
    # }
    #
    # and:
    #
    # {
    #     "affine": {
    #         "x_half_ratio": ...,
    #         "y_half_ratio": ...,
    #         "z_half_ratio": ...
    #     }
    # }
    # ------------------------------------------------------------

    if "affine" in params:

        affine = params["affine"]

        if not isinstance(
            affine,
            dict
        ):

            raise RuntimeError(
                "'affine' must be a JSON object."
            )

        return affine

    return params


# ================================================================
# LOAD ROTATION
# ================================================================

def load_rotation():

    # ------------------------------------------------------------
    # Preferred interface:
    #
    # DATASET_ROTATION_JSON
    # ------------------------------------------------------------

    rotation_raw = os.environ.get(
        "DATASET_ROTATION_JSON"
    )

    if rotation_raw is not None:

        if rotation_raw.strip() == "":

            raise RuntimeError(
                "DATASET_ROTATION_JSON is empty."
            )

        print("")
        print(
            "DATASET_ROTATION_JSON:"
        )

        print(
            rotation_raw
        )

        try:

            rotation = json.loads(
                rotation_raw
            )

        except Exception as exc:

            raise RuntimeError(
                "Invalid DATASET_ROTATION_JSON:\n"
                + str(exc)
            )

        return rotation

    # ------------------------------------------------------------
    # Backwards compatibility:
    #
    # Allow rotation inside DATASET_PARAMS_JSON.
    # ------------------------------------------------------------

    raw = os.environ.get(
        "DATASET_PARAMS_JSON"
    )

    if raw is not None:

        try:

            params = json.loads(
                raw
            )

        except Exception:

            params = {}

        if isinstance(
            params,
            dict
        ):

            if "rotation" in params:

                return params["rotation"]

            if "affine" in params:

                affine = params["affine"]

                if isinstance(
                    affine,
                    dict
                ):

                    if "rotation" in affine:

                        return affine["rotation"]

    # ------------------------------------------------------------
    # Dataset interface uses independent rotation.
    # ------------------------------------------------------------

    raise RuntimeError(
        "Missing rotation parameter.\n"
        "Expected DATASET_ROTATION_JSON."
    )


# ================================================================
# FLOAT PARAMETER
# ================================================================

def get_float(
    params,
    name
):

    if name not in params:

        raise RuntimeError(
            "Missing affine parameter: {}\n"
            "Received: {}".format(
                name,
                params
            )
        )

    try:

        value = float(
            params[name]
        )

    except Exception:

        raise RuntimeError(
            "Affine parameter '{}' "
            "must be numeric.".format(name)
        )

    if not math.isfinite(value):

        raise RuntimeError(
            "Affine parameter '{}' "
            "must be finite.".format(name)
        )

    return value


# ================================================================
# AFFINE -> PHYSICAL REALIZATION
# ================================================================

def realize_box_dimensions(
    affine
):

    x_half_ratio = get_float(
        affine,
        "x_half_ratio"
    )

    y_half_ratio = get_float(
        affine,
        "y_half_ratio"
    )

    z_half_ratio = get_float(
        affine,
        "z_half_ratio"
    )

    # ------------------------------------------------------------
    # Validate.
    # ------------------------------------------------------------

    if x_half_ratio <= 0.0:

        raise RuntimeError(
            "x_half_ratio must be > 0."
        )

    if y_half_ratio <= 0.0:

        raise RuntimeError(
            "y_half_ratio must be > 0."
        )

    if z_half_ratio <= 0.0:

        raise RuntimeError(
            "z_half_ratio must be > 0."
        )

    # ------------------------------------------------------------
    # ONLY dimensional realization in the macro.
    #
    # The generator provides half-dimensions in affine space.
    #
    # physical half-dimension =
    #
    #     ratio * REALIZATION_SCALE_MM
    # ------------------------------------------------------------

    x_half_mm = (
        x_half_ratio
        * REALIZATION_SCALE_MM
    )

    y_half_mm = (
        y_half_ratio
        * REALIZATION_SCALE_MM
    )

    z_half_mm = (
        z_half_ratio
        * REALIZATION_SCALE_MM
    )

    # Full dimensions.

    x_size_mm = (
        2.0
        * x_half_mm
    )

    y_size_mm = (
        2.0
        * y_half_mm
    )

    z_size_mm = (
        2.0
        * z_half_mm
    )

    return (
        x_half_mm,
        y_half_mm,
        z_half_mm,
        x_size_mm,
        y_size_mm,
        z_size_mm
    )


# ================================================================
# QUATERNION -> FREECAD ROTATION
# ================================================================

def quaternion_to_rotation(
    quaternion
):

    if quaternion is None:

        raise RuntimeError(
            "Rotation is None."
        )

    if not isinstance(
        quaternion,
        (list, tuple)
    ):

        raise RuntimeError(
            "Rotation must be a list "
            "[qx, qy, qz, qw]."
        )

    if len(quaternion) != 4:

        raise RuntimeError(
            "Rotation must contain exactly "
            "four values: [qx, qy, qz, qw]."
        )

    try:

        qx = float(
            quaternion[0]
        )

        qy = float(
            quaternion[1]
        )

        qz = float(
            quaternion[2]
        )

        qw = float(
            quaternion[3]
        )

    except Exception:

        raise RuntimeError(
            "Quaternion components must be numeric."
        )

    # ------------------------------------------------------------
    # Validate finite values.
    # ------------------------------------------------------------

    components = (
        qx,
        qy,
        qz,
        qw
    )

    for value in components:

        if not math.isfinite(value):

            raise RuntimeError(
                "Quaternion components must be finite."
            )

    # ------------------------------------------------------------
    # Normalize quaternion.
    # ------------------------------------------------------------

    norm = math.sqrt(
        qx * qx
        + qy * qy
        + qz * qz
        + qw * qw
    )

    if norm < 1e-15:

        raise RuntimeError(
            "Rotation quaternion has zero length."
        )

    qx /= norm
    qy /= norm
    qz /= norm
    qw /= norm

    # ------------------------------------------------------------
    # Quaternion -> axis-angle.
    # ------------------------------------------------------------

    sin_half = math.sqrt(
        qx * qx
        + qy * qy
        + qz * qz
    )

    # Identity rotation.

    if sin_half < 1e-12:

        return App.Rotation()

    axis = App.Vector(
        qx / sin_half,
        qy / sin_half,
        qz / sin_half
    )

    angle_rad = (
        2.0
        * math.atan2(
            sin_half,
            qw
        )
    )

    angle_deg = (
        angle_rad
        * 180.0
        / math.pi
    )

    return App.Rotation(
        axis,
        angle_deg
    )


# ================================================================
# CREATE BOX
# ================================================================

def create_box(
    x_half_mm,
    y_half_mm,
    z_half_mm,
    rotation
):

    # ------------------------------------------------------------
    # Create canonical box centered at origin.
    #
    # X:
    #     [-x_half, +x_half]
    #
    # Y:
    #     [-y_half, +y_half]
    #
    # Z:
    #     [-z_half, +z_half]
    #
    # This is important because rotation is performed around
    # the canonical origin.
    # ------------------------------------------------------------

    x_size_mm = (
        2.0
        * x_half_mm
    )

    y_size_mm = (
        2.0
        * y_half_mm
    )

    z_size_mm = (
        2.0
        * z_half_mm
    )

    shape = Part.makeBox(
        x_size_mm,
        y_size_mm,
        z_size_mm,
        App.Vector(
            -x_half_mm,
            -y_half_mm,
            -z_half_mm
        )
    )

    if shape is None:

        raise RuntimeError(
            "FreeCAD failed to create the box."
        )

    if shape.isNull():

        raise RuntimeError(
            "FreeCAD created a null box shape."
        )

    # ------------------------------------------------------------
    # Apply rotation around the canonical origin.
    #
    # No translation is applied.
    # ------------------------------------------------------------

    shape.Placement = App.Placement(
        App.Vector(
            0.0,
            0.0,
            0.0
        ),
        rotation
    )

    if shape.isNull():

        raise RuntimeError(
            "Box shape became null after rotation."
        )

    return shape


# ================================================================
# STL EXPORT
# ================================================================

def export_shape_as_stl(
    shape,
    output_path
):

    if shape is None:

        raise RuntimeError(
            "No shape was generated."
        )

    if shape.isNull():

        raise RuntimeError(
            "Generated shape is null."
        )

    output_dir = os.path.dirname(
        output_path
    )

    if output_dir:

        os.makedirs(
            output_dir,
            exist_ok=True
        )

    angular_rad = (
        ANGULAR_DEFLECTION_DEG
        * math.pi
        / 180.0
    )

    mesh = MeshPart.meshFromShape(
        Shape=shape,
        LinearDeflection=LINEAR_DEFLECTION_MM,
        AngularDeflection=angular_rad,
        Relative=RELATIVE_MESH
    )

    if mesh is None:

        raise RuntimeError(
            "MeshPart.meshFromShape() returned None."
        )

    mesh.write(
        output_path
    )

    # ------------------------------------------------------------
    # Verify STL.
    # ------------------------------------------------------------

    if not os.path.isfile(
        output_path
    ):

        raise RuntimeError(
            "STL was not created:\n"
            + output_path
        )

    size = os.path.getsize(
        output_path
    )

    if size <= 0:

        raise RuntimeError(
            "STL file is empty:\n"
            + output_path
        )

    print("")
    print(
        "STL created successfully:"
    )

    print(
        " ",
        output_path
    )

    print(
        " ",
        size,
        "bytes"
    )


# ================================================================
# MAIN
# ================================================================

def main():

    print("")
    print(
        "============================================================"
    )

    print(
        "AFFINE BOX DATASET MACRO"
    )

    print(
        "============================================================"
    )

    print(
        "Physical realization scale =",
        REALIZATION_SCALE_MM,
        "mm"
    )

    # ------------------------------------------------------------
    # Load affine parameters.
    # ------------------------------------------------------------

    affine = load_affine_parameters()

    print("")
    print(
        "Affine parameters:"
    )

    print(
        json.dumps(
            affine,
            indent=2
        )
    )

    # ------------------------------------------------------------
    # Load rotation independently.
    # ------------------------------------------------------------

    quaternion = load_rotation()

    print("")
    print(
        "Rotation:"
    )

    print(
        quaternion
    )

    # ------------------------------------------------------------
    # Output STL.
    # ------------------------------------------------------------

    output_path = require_environment_variable(
        "DATASET_OUT_STL"
    )

    print("")
    print(
        "Output STL:"
    )

    print(
        output_path
    )

    # ------------------------------------------------------------
    # Realize affine geometry.
    # ------------------------------------------------------------

    (
        x_half_mm,
        y_half_mm,
        z_half_mm,
        x_size_mm,
        y_size_mm,
        z_size_mm
    ) = realize_box_dimensions(
        affine
    )

    print("")
    print(
        "Physical realization:"
    )

    print(
        "  x half =",
        x_half_mm,
        "mm"
    )

    print(
        "  y half =",
        y_half_mm,
        "mm"
    )

    print(
        "  z half =",
        z_half_mm,
        "mm"
    )

    print(
        "  x size =",
        x_size_mm,
        "mm"
    )

    print(
        "  y size =",
        y_size_mm,
        "mm"
    )

    print(
        "  z size =",
        z_size_mm,
        "mm"
    )

    # ------------------------------------------------------------
    # Convert rotation.
    # ------------------------------------------------------------

    rotation = quaternion_to_rotation(
        quaternion
    )

    # ------------------------------------------------------------
    # Create canonical centered box and rotate it.
    # ------------------------------------------------------------

    shape = create_box(
        x_half_mm=x_half_mm,
        y_half_mm=y_half_mm,
        z_half_mm=z_half_mm,
        rotation=rotation
    )

    # ------------------------------------------------------------
    # Export STL.
    # ------------------------------------------------------------

    export_shape_as_stl(
        shape=shape,
        output_path=output_path
    )

    print("")
    print(
        "Box sample completed successfully."
    )

    print(
        "============================================================"
    )


# ================================================================
# RUN
# ================================================================

if __name__ == "__main__":

    main()
